# FCUpdate
#
# Copyright (C) 2025 Grubuntu
#
# This library is free software; you can redistribute it and/or
# modify it under the terms of the GNU Lesser General Public
# License as published by the Free Software Foundation; either
# version 2.1 of the License, or (at your option) any later version.
#
# This library is distributed in the hope that it will be useful,
# but WITHOUT ANY WARRANTY; without even the implied warranty of
# MERCHANTABILITY or FITNESS FOR A PARTICULAR PURPOSE.  See the GNU
# Lesser General Public License for more details.
#
# You should have received a copy of the GNU Lesser General Public
# License along with this library; if not, write to the Free Software
# Foundation, Inc., 51 Franklin Street, Fifth Floor, Boston, MA  02110-1301 USA

# Attribution:
# http://forum.freecadweb.org/
# http://www.freecadweb.org/wiki/index.php?title=Code_snippets
#

# voir pour afficher la version actuelle et mettre en valeur la mise à jour dispo

# === Contenu du fichier InitGui.py ===
init_gui_content = '''\
from PySide import QtGui
import FreeCAD as App

# auto start code at FreeCAD launch
def runStartupMacros(name):

    if name != "NoneWorkbench":
        Gui.getMainWindow().workbenchActivated.disconnect(runStartupMacros)
        import FCUpdate
        FCUpdate.run()

import __main__
__main__.runStartupMacros = runStartupMacros

Gui.getMainWindow().workbenchActivated.connect(runStartupMacros)
'''

# === Contenu du fichier FCUpdate.py ===
check_update_content = '''\
FCUPDATEVERSION = "1.4"

import os
import re
import sys
import json
import time
import webbrowser
import requests
from datetime import datetime, timedelta
from pathlib import Path
from PySide import QtGui, QtCore, QtWidgets
import FreeCAD as App
import FreeCADGui as Gui
from functools import partial
from PySide.QtCore import QTimer, QPoint
from PySide.QtWidgets import QToolTip, QToolBar
translate = App.Qt.translate



# Add translations path
Gui.addLanguagePath(os.path.join(os.path.dirname(__file__), "translations"))
Gui.updateLocale()

# === CONFIGURATION ===
URL_RELEASES = "https://api.github.com/repos/FreeCAD/FreeCAD/releases?per_page=20"

MINIMUM_CHECK_INTERVAL = timedelta(hours=1)

def get_freecad_config_dir():
    if sys.platform == "win32":
        return os.path.join(os.getenv("APPDATA"), "FreeCAD")
    elif sys.platform == "darwin":
        return os.path.join(os.path.expanduser("~"), "Library", "Preferences", "FreeCAD")
    else:
        return os.path.join(os.path.expanduser("~"), ".config", "FreeCAD")

CONFIG_DIR = get_freecad_config_dir()
CONFIG_FILE = os.path.join(CONFIG_DIR, "FCUpdate.cfg")
CACHE_FILE = os.path.join(CONFIG_DIR, "FCUpdate_cache.txt")
os.makedirs(CONFIG_DIR, exist_ok=True)

ICON_CHECK = QtGui.QApplication.style().standardIcon(QtGui.QStyle.SP_BrowserReload)
ICON_UPDATE = QtGui.QApplication.style().standardIcon(QtGui.QStyle.SP_DialogOkButton)
ICON_RELEASE = QtGui.QApplication.style().standardIcon(QtGui.QStyle.SP_FileDialogContentsView)
ICON_ABOUT = QtGui.QApplication.style().standardIcon(QtGui.QStyle.SP_MessageBoxInformation)

t = QtCore.QTimer()
mw = Gui.getMainWindow()

menuFCUpdate = QtGui.QMenu("FCUpdate", mw)
menuFCUpdate.setObjectName("FCUpdateMenu")
menuFCUpdate.setVisible(True)

iconeFCUpdate = QtGui.QMenu("", mw)
iconeFCUpdate.setIcon(ICON_UPDATE)
iconeFCUpdate.setObjectName("FCUpdateMenu")

sousMenuUpdate = QtGui.QAction(mw)

updateVersionText = translate("Update Menu", "No update available !")
update_available = False
display_update_window = None



#### ajout d'un bouton pour masquer/afficher la console dans la barre d'état ####
from PySide6 import QtWidgets
import FreeCADGui as Gui

# Récupère la fenêtre principale de FreeCAD
mw = Gui.getMainWindow()
sb = mw.statusBar()

# Fonction de bascule pour la console Python et la vue Rapport
def toggle_console_and_report():
    py_console = mw.findChild(QtWidgets.QDockWidget, "Python console")
    report_view = mw.findChild(QtWidgets.QDockWidget, "Report view")
    
    if py_console and report_view:
        visible = py_console.isVisible() or report_view.isVisible()
        py_console.setVisible(not visible)
        report_view.setVisible(not visible)

# Crée le bouton
btn_toggle = QtWidgets.QPushButton("Afficher/Masquer Console")
btn_toggle.setToolTip("Afficher ou masquer la console Python et la vue Rapport")
btn_toggle.clicked.connect(toggle_console_and_report)

# Ajoute le bouton à la barre de statut (à droite)
sb.insertPermanentWidget(2, btn_toggle)

#### ####


# === FONCTIONS VERSIONS ===
# get type of version : Stable or Dev(Weekly)
def get_freecad_version_type():
    version_info = App.Version()

    if len(version_info) < 6:
        return "FreeCAD (Unknown version)"

    major, minor, patch = version_info[0:3]
    build_info = version_info[3]
    repo_url = version_info[4]
    git_branch = version_info[6] if len(version_info) > 6 else ""
    git_tag = version_info[7] if len(version_info) > 7 else ""

    version_text = str(App.Version())

    # Détection Stable
    if "detached at" in git_branch:
        if major and minor:
            return ("FreeCAD {}.{}.x Stable").format(major, minor)
        return "FreeCAD Stable Release"

    # Détection Weekly
    if "main" in repo_url.lower():
        return "FreeCAD Weekly Build"

    return (translate("MainWindow", "FreeCAD customised or unknown version"))

# get current version of FreeCAD
def get_local_build_date():
    date_str = App.Version()[5]
    try:
        return datetime.strptime(date_str, '%Y/%m/%d %H:%M:%S')
    except ValueError:
        try:
            return datetime.strptime(date_str, '%Y/%m/%d')
        except ValueError:
            App.Console.PrintError(translate("MainWindow", "Error parsing local build date: {}").format(date_str))
            return None

# get last weekly version in cache
def get_remote_weekly_date():
    _, results = read_cache()
    try:
        for entry in results:
            name = entry[0]
            if name.startswith("FreeCAD_weekly-") and "-Windows-x86_64" in name:
                match = re.search(r"FreeCAD_weekly-(\d{4}\.\d{2}\.\d{2})-", name)
                if match:
                    date_str = match.group(1)
                    return datetime.strptime(date_str, '%Y.%m.%d')
        return None
    except Exception as e:
        App.Console.PrintError(
            translate("MainWindow", "Error retrieving online weekly date: {}").format(e)
        )
        
        return None

# get last stable version in cache
def get_remote_stable_version():
    _, results = read_cache()
    for ligne in results:
        if isinstance(ligne, list) and isinstance(ligne[0], str):
            match = re.search(r"FreeCAD[_-](\d+\.\d+\.\d+)", ligne[0])
            if match:
                return match.group(1)
    return None

def parse_version(version_str):
    return tuple(map(int, version_str.split('.')))

# === CACHE ===
# read data in cache to limit API access 
def read_cache():
    if not os.path.exists(CACHE_FILE):
        return None, []
    try:
        with open(CACHE_FILE, "r") as f:
            content = f.read().strip()
            if not content:
                return None, []

            data = json.loads(content)

            last_check_str = data.get("last_check", "")
            try:
                last_check = datetime.fromisoformat(last_check_str) if last_check_str else None
            except ValueError:
                last_check = None

            results = data.get("results_cache", [])
            return last_check, results
    except Exception as e:
        print("❌ Erreur lors de la lecture du cache :", e)
        return None, []

def write_cache(last_check, results_cache):
    try:
        os.makedirs(CONFIG_DIR, exist_ok=True)

        with open(CACHE_FILE, "w") as f:
            json.dump({
                "last_check": last_check.isoformat() if last_check else "",
                "results_cache": results_cache
            }, f, indent=4)
            f.flush()
            os.fsync(f.fileno())

    except Exception as e:
        print("❌ Erreur d’écriture du cache de FCUpdate:", e)
        
# construct list of files available
def fetch_all_files(forceReload=False):
    now = datetime.now()
    last_check, cached_results = read_cache()
    global update_available
    results = []
    def fetch():
        try:
            r = requests.get(URL_RELEASES, timeout=10)
            r.raise_for_status()
            releases = r.json()
            latest_stable = None
            latest_dev = None
            for release in releases:
                if not release["draft"]:
                    if not release["prerelease"] and not latest_stable:
                        latest_stable = release
                    if release["prerelease"] and not latest_dev:
                        latest_dev = release
                if latest_stable and latest_dev:
                    break
            if latest_stable:
                results.append((translate("Table", "Canal Stable :"), ""))
                for asset in latest_stable.get("assets", []):
                    name = asset.get("name", "")
                    durl = asset.get("browser_download_url", "")
                    results.append((name, durl))
            if latest_dev:
                results.append((translate("Table", "Canal Development :"), ""))
                for asset in latest_dev.get("assets", []):
                    name = asset.get("name", "")
                    durl = asset.get("browser_download_url", "")
                    results.append((name, durl))
        except Exception as e:
            App.Console.PrintError(translate("Console", "❌ Error retrieving releases: {}").format(e))

    if not last_check or now - last_check > MINIMUM_CHECK_INTERVAL or forceReload:
        fetch()
        write_cache(now, results)
    else:
        results = cached_results

    return results

# === BOUTON / INTERFACE ===
# add menu FCUpdate in FreeCAD
def waitFreeCADReady():
    mw = Gui.getMainWindow()
    startAM = False
    try:
        mw.mainWindowClosed
        mw.workbenchActivated
        startAM = True
    except AttributeError:
        pass
    if startAM:
        t.stop()
        t.deleteLater()
        addMenu()
        mw = Gui.getMainWindow()
        mw.workbenchActivated.connect(addMenu)

def addMenu():
    mw = Gui.getMainWindow()
    action = mw.findChild(QtGui.QAction, "Check Updates")
    if not action:

        sousMenu1 = QtGui.QAction(mw)
        sousMenu1.setText(translate("Menu", "Check Updates"))
        sousMenu1.setIcon(ICON_CHECK)
        sousMenu1.setObjectName("Check Updates")
        sousMenu1.triggered.connect(lambda: check_for_updates(True))

        sousMenu2 = QtGui.QAction(mw)
        sousMenu2.setText(translate("Menu", "FreeCAD Releases..."))
        sousMenu2.setIcon(ICON_RELEASE)
        sousMenu2.setObjectName("FreeCAD Releases...")
        sousMenu2.triggered.connect(display_freecad_update)
        
        sousMenu3 = QtGui.QAction(mw)
        sousMenu3.setText(translate("Menu", "Infos FCUpdate"))
        sousMenu3.setIcon(ICON_ABOUT)
        sousMenu3.setEnabled(True)
        sousMenu3.setObjectName("Infos FCUpdate")
        sousMenu3.triggered.connect(infoPopup)

        # sousMenuUpdate = QtGui.QAction(mw)
        sousMenuUpdate.setText(translate("Menu", updateVersionText))
        sousMenuUpdate.setEnabled(True)
        sousMenuUpdate.setObjectName("SousMenuUpdate")
        sousMenuUpdate.triggered.connect(display_freecad_update)

        menuFCUpdate.addAction(sousMenu1)
        menuFCUpdate.addAction(sousMenu2)
        menuFCUpdate.addAction(sousMenu3)

    mw.menuBar().addMenu(menuFCUpdate)
    mw.menuBar().addMenu(iconeFCUpdate)

    iconeFCUpdate.menuAction().setVisible(update_available)
    iconeFCUpdate.addAction(sousMenuUpdate)
    return menuFCUpdate

def infoPopup():
    msg = """
        <h2>FCUpdate</h2>
        <p style='font-weight:normal;font-style:italic;'>version """ + FCUPDATEVERSION + """</p>
        <p style='font-weight:normal;'>FCUpdate help to easily retrieve FreeCAD update from github server.</p>
        <p>Visit <a href='https://github.com/Grubuntu/FCUpdate/'>https://github.com/Grubuntu/FCUpdate/</a></p>
        <hr>
        <h2>Licence</h2>
        <p style='font-weight:normal;'>Copyright (C) 2025 Grubuntu</p>
      
        <p style='font-weight:normal;'>This library is free software; you can redistribute it and/or modify it under the terms of the GNU Lesser General Public License as published by the Free Software Foundation; either version 2.1 of the License, or (at your option) any later version.</p>
        <p style='font-weight:normal;'>This library is distributed in the hope that it will be useful, but WITHOUT ANY WARRANTY; without even the implied warranty of MERCHANTABILITY or FITNESS FOR A PARTICULAR PURPOSE.  See the GNU Lesser General Public License for more details.</p>
        <p style='font-weight:normal;'>You should have received a copy of the GNU Lesser General Public License along with this library; if not, write to the Free Software Foundation, Inc., 51 Franklin Street, Fifth Floor, Boston, MA  02110-1301 USA</p>
    """
    QtGui.QMessageBox.question(None, "Help", msg, QtGui.QMessageBox.Ok)

def check_for_updates(showMessage=False):
    global update_available
    mw = App.Gui.getMainWindow()

    version_type = get_freecad_version_type()
    local = None
    remote = None

    fetch_all_files(False)

    if "Weekly" in version_type:
        local = get_local_build_date()
        remote = get_remote_weekly_date()
        local_display = local.strftime('%Y.%m.%d') if local else "Unknown"
        remote_display = remote.strftime('%Y.%m.%d') if remote else "Unknown"
    elif "Stable" in version_type:
        local_str = ".".join(App.Version()[0:3])
        remote_str = get_remote_stable_version()
        local = parse_version(local_str) if local_str else None
        remote = parse_version(remote_str) if remote_str else None
        local_display = local_str
        remote_display = remote_str
    else:
        if showMessage:
            tooltip = translate("Tooltip", "⁉️ Unable to identify the current version.")
            QtGui.QMessageBox.warning(None, "Error", tooltip)
        return False

    if remote and local and remote > local:
        delta = remote - local
        if delta.days >= 2:
            update_available = True
            global updateVersionText
            updateVersionText = translate("Update Menu", "New version available : {}").format(remote_display)
            if showMessage:
                msg_box = QtGui.QMessageBox()
                msg_box.setIcon(QtGui.QMessageBox.Information)
                msg_box.setWindowTitle(translate("Update Message","Update available"))
                msg_box.setText(translate("Update Message", "FreeCAD new version is available."))
                msg_box.setInformativeText(translate("Dialog", "Current version : {}" "\\nNew version available : {}").format(local_display, remote_display))
                msg_box.setStandardButtons(QtGui.QMessageBox.Ok | QtGui.QMessageBox.Close)
                result = msg_box.exec()

                if result == QtGui.QMessageBox.Ok:
                    display_freecad_update()

    else:
        updateVersionText = (translate("Update Menu", "No update."))
        if showMessage:
            QtGui.QMessageBox.information(
                None, translate("Update Message", 
                "No update available !"),
                translate("Update Message", "No update available !")
            )

    iconeFCUpdate.menuAction().setVisible(update_available)
    return update_available

def load_config():
    if not os.path.exists(CONFIG_FILE):
        return {}

    try:
        with open(CONFIG_FILE, "r") as f:
            content = f.read().strip()
            if not content:
                # Fichier vide
                return {}
            return json.loads(content)
    except (json.JSONDecodeError, IOError) as e:
        # Optionnel : print ou logger l'erreur
        print(f"Erreur en lisant le fichier de config : {e}")
        return {}

def save_config(config):
    # Charger le cache existant
    if os.path.exists(CONFIG_FILE):
        try:
            with open(CONFIG_FILE, "r") as f:
                existing = json.load(f)
        except Exception:
            existing = {}
    else:
        existing = {}

    existing.update(config)
    os.makedirs(CONFIG_DIR, exist_ok=True)
    with open(CONFIG_FILE, "w") as f:
        json.dump(existing, f, indent=4)

def get_file_type(file_name):
    if file_name.endswith("SHA256.txt") or "SHA256" in file_name:
        return "SHA256"
    elif file_name.endswith(".exe") or "Windows" in file_name:
        return "Windows"
    elif file_name.endswith(".AppImage") or "Linux" in file_name:
        return "Linux"
    elif file_name.endswith(".dmg") or "macOS" in file_name:
        return "macOS"
    elif file_name.endswith(".tar.gz") or file_name.endswith(".zip"):
        return "source"
    return "Other"


# === FENÊTRE PRINCIPALE ===
class FreeCADUpdateChecker(QtWidgets.QDialog):
    def __init__(self):
        super().__init__()
        self.setWindowTitle("FCUpdate " + FCUPDATEVERSION)
        self.setFixedSize(600, 600)
        self.setWindowFlags(QtCore.Qt.Window | QtCore.Qt.WindowStaysOnTopHint)
        self.setPalette(QtWidgets.QApplication.palette())
        self.setModal(True)
        self.results = []
        self.setup_ui()
        # Appel initial du filtre si des fichiers sont déjà chargés
        self.apply_filter()
        self.load_data(False)

    def setup_ui(self):
        layout = QtWidgets.QVBoxLayout(self)

        self.liste_files = QtWidgets.QTableWidget(0, 2)
        self.liste_files.horizontalHeader().setVisible(False)
        self.liste_files.verticalHeader().setVisible(False)
        self.liste_files.setEditTriggers(QtWidgets.QAbstractItemView.NoEditTriggers)
        self.liste_files.setSelectionBehavior(QtWidgets.QAbstractItemView.SelectRows)
        self.liste_files.setHorizontalScrollBarPolicy(QtCore.Qt.ScrollBarAlwaysOff)
        self.liste_files.setSizePolicy(QtWidgets.QSizePolicy.Expanding, QtWidgets.QSizePolicy.Expanding)
        self.liste_files.horizontalHeader().setSectionResizeMode(0, QtWidgets.QHeaderView.Stretch)

        self.filter_checkboxes = {}
        filter_layout = QtWidgets.QHBoxLayout()

        filter_types = ["Windows", "Linux", "macOS", "source", "SHA256"]
        self.config = load_config()

        for name in filter_types:
            cb = QtWidgets.QCheckBox(name)
            cb.setChecked(self.config.get("filter_" + name, True))
            cb.stateChanged.connect(self.apply_filter)
            self.filter_checkboxes[name] = cb
            filter_layout.addWidget(cb)

        self.status_label = QtWidgets.QLabel(translate("Status", "Loading..."))
        self.status_label.setAlignment(QtCore.Qt.AlignCenter)
        self.status_label.setMargin(10)

        button_layout = QtWidgets.QHBoxLayout()
        update_btn = QtWidgets.QPushButton(translate("MainWindow", "Reload"))
        update_btn.setToolTip("Force update check now")
        update_btn.clicked.connect(lambda: self.load_data(True))
        close_btn = QtWidgets.QPushButton(translate("MainWindow", "Close"))
        close_btn.setToolTip("Close this window")
        close_btn.clicked.connect(self.close)

        button_layout.addWidget(update_btn)
        button_layout.addWidget(close_btn)

        layout.addWidget(self.liste_files)
        layout.addLayout(filter_layout)
        layout.addWidget(self.status_label)
        layout.addLayout(button_layout)

    def apply_filter(self):
        for key, cb in self.filter_checkboxes.items():
            self.config["filter_" + key] = cb.isChecked()
        save_config(self.config)

        for row in range(self.liste_files.rowCount()):
            item = self.liste_files.item(row, 0)
            if item is None:
                continue
            data_type = item.data(QtCore.Qt.UserRole)

            if data_type == "section":
                self.liste_files.setRowHidden(row, False)
            else:
                file_name = item.text()
                file_type = get_file_type(file_name)

                # Premier filtre : est-ce que ce type est coché ?
                is_checked = self.filter_checkboxes.get(file_type, QtWidgets.QCheckBox()).isChecked()

                # Deuxième filtre pour SHA256 : ne s'affiche que si un fichier associé est visible
                if file_type == "SHA256":
                    visible = False
                    for os_type in ("Windows", "Linux", "macOS", "source"):
                        if os_type in file_name and self.filter_checkboxes.get(os_type, QtWidgets.QCheckBox()).isChecked():
                            visible = True
                            break
                    # Et bien sûr, il faut aussi que SHA256 soit coché
                    visible = visible and is_checked
                else:
                    visible = is_checked

                self.liste_files.setRowHidden(row, not visible)

    def load_data(self, forceReload):
        self.results = fetch_all_files(forceReload)
        now = datetime.now()
        last_check, cached_results = read_cache()
        minutes = int((now - last_check).total_seconds() // 60)
        if update_available :
            self.status_label.setText(translate("Status", "Last check {} minutes ago. {}").format(minutes, updateVersionText))
        else:
            self.status_label.setText(translate("Status", "Last check {} minutes ago. {}").format(minutes, updateVersionText))
        self.update_ui(self.results)

    # update list of files in tablewidget
    def update_ui(self, results):
        self.liste_files.setRowCount(0)

        for name, url in results:
            row = self.liste_files.rowCount()
            self.liste_files.insertRow(row)

            item_name = QtWidgets.QTableWidgetItem(name)
            item_name.setFlags(QtCore.Qt.ItemIsEnabled)

            if not url:
                font = item_name.font()
                font.setBold(True)
                item_name.setFont(font)
                item_name.setBackground(QtGui.QColor("#777777"))
                item_name.setFlags(QtCore.Qt.ItemIsEnabled)
                item_name.setData(QtCore.Qt.UserRole, "section")  # Marque comme section
                self.liste_files.setSpan(row, 0, 1, 2)
                self.liste_files.setItem(row, 0, item_name)
            else:
                item_name.setData(QtCore.Qt.UserRole, "file")  # Marque comme fichier
                btn = QtWidgets.QPushButton(translate("Table", "Download"))
                btn.clicked.connect(partial(webbrowser.open, url))
                self.liste_files.setItem(row, 0, item_name)
                self.liste_files.setCellWidget(row, 1, btn)
        self.apply_filter()

# === LANCEMENT ===
def display_freecad_update():
    global display_update_window
    display_update_window = FreeCADUpdateChecker()
    display_update_window.setWindowFlags(QtCore.Qt.Window)
    display_update_window.setWindowIcon(QtGui.QIcon(":/icons/freecad"))
    display_update_window.setAttribute(QtCore.Qt.WA_DeleteOnClose, True)
    display_update_window.destroyed.connect(clear_reference)
    display_update_window.show()

def clear_reference():
    global display_update_window
    display_update_window = None

# t = QtCore.QTimer()

def run():
    t.timeout.connect(waitFreeCADReady)
    t.start(500)
    if App.GuiUp:
        check_for_updates()
    else:
        print(translate("Console", "This macro requires FreeCAD graphique interface."))

'''

import os
import socket
import json
import locale
import platform
import urllib.request
from pathlib import Path
from PySide import QtCore, QtGui, QtWidgets
from PySide.QtWidgets import (
    QMessageBox, QCheckBox, QDialog, QVBoxLayout,
    QLabel, QPushButton, QDialogButtonBox, QProgressDialog
)

# --- Internals translations ---
locales_table = {'English': 'en', 'Afrikaans': 'af', 'Arabic': 'ar', 'Basque': 'eu', 'Catalan': 'ca', 'Chinese Simplified': 'zh-CN', 'Chinese Traditional': 'zh-TW', 'Croatian': 'hr', 'Czech': 'cs', 'Dutch': 'nl', 'Filipino': 'fil', 'Finnish': 'fi', 'French': 'fr', 'Galician': 'gl', 'German': 'de', 'Hungarian': 'hu', 'Indonesian': 'id', 'Italian': 'it', 'Japanese': 'ja', 'Kabyle': 'kab', 'Korean': 'ko', 'Lithuanian': 'lt', 'Norwegian': 'no', 'Polish': 'pl', 'Portuguese': 'pt-PT', 'Portuguese, Brazilian': 'pt-BR', 'Romanian': 'ro', 'Russian': 'ru', 'Slovak': 'sk', 'Slovenian': 'sl', 'Spanish': 'es-ES', 'Swedish': 'sv-SE', 'Turkish': 'tr', 'Ukrainian': 'uk', 'Valencian': 'val-ES', 'Vietnamese': 'vi'}

translations = {
    'French': {
        "FCUpdate installation": "Installation de FCUpdate",
        "This macro will create a folder in your user space to install the files needed to check for FreeCAD updates. If FCUpdate is already installed, the files will be overwritten. \n Would you like to continue ?":
            "Cette macro va créer un dossier dans votre espace utilisateur pour installer les fichiers nécessaires à la vérification des mises à jour de FreeCAD. Si FCUpdate est déjà installé, les fichiers seront écrasés.\nSouhaitez-vous continuer ?",
        "Install language packs": "Installer les packs de langue",
        "Yes": "Oui",
        "No": "Non",
        "Error": "Erreur",
        "No Internet connection": "Pas de connexion Internet",
        "Could not download translations because the computer is offline.": "Impossible de télécharger les traductions car l'ordinateur est hors ligne.",
        "FCUpdate successfully installed.": "FCUpdate a été installé avec succès.",
        "Please restart FreeCAD for changes to take effect.\nRestart FreeCAD?": "Veuillez redémarrer FreeCAD pour que les modifications prennent effet.\nRedémarrer FreeCAD ?",
        "Restart Required": "Redémarrage requis",
        "Now": "Maintenant",
        "Later": "Plus tard",
        "Installation cancelled": "Installation annulée",
        "No files have been installed.": "Aucun fichier n’a été installé.",
    },
    'German': {
        "FCUpdate installation": "Installation des FCUpdate",
        "This macro will create a folder in your user space to install the files needed to check for FreeCAD updates. If FCUpdate is already installed, the files will be overwritten. \n Would you like to continue ?":
            "Dieses Makro erstellt einen Ordner in Ihrem Benutzerverzeichnis, um die Dateien zu installieren, die zum Überprüfen von FreeCAD-Updates erforderlich sind. Wenn FCUpdate bereits installiert ist, werden die Dateien überschrieben.\nMöchten Sie fortfahren?",
        "Install language packs": "Sprachpakete installieren",
        "Yes": "Ja",
        "No": "Nein",
        "Error": "Fehler",
        "No Internet connection": "Keine Internetverbindung",
        "Could not download translations because the computer is offline.": "Übersetzungen konnten nicht heruntergeladen werden, da der Computer offline ist.",
        "FCUpdate successfully installed.": "FCUpdate wurde erfolgreich installiert.",
        "Please restart FreeCAD for changes to take effect.\nRestart FreeCAD?": "Bitte starten Sie FreeCAD neu, damit die Änderungen wirksam werden.\nFreeCAD jetzt neu starten?",
        "Restart Required": "Neustart erforderlich",
        "Now": "Jetzt",
        "Later": "Später",
        "Installation cancelled": "Installation abgebrochen",
        "No files have been installed.": "Es wurden keine Dateien installiert.",
    },
    'Spanish': {
        "FCUpdate installation": "Instalación de FCUpdate",
        "This macro will create a folder in your user space to install the files needed to check for FreeCAD updates. If FCUpdate is already installed, the files will be overwritten. \n Would you like to continue ?":
            "Esta macro creará una carpeta en tu espacio de usuario para instalar los archivos necesarios para comprobar las actualizaciones de FreeCAD. Si FCUpdate ya está instalado, los archivos serán sobrescritos.\n¿Deseas continuar?",
        "Install language packs": "Instalar paquetes de idioma",
        "Yes": "Sí",
        "No": "No",
        "Error": "Error",
        "No Internet connection": "Sin conexión a Internet",
        "Could not download translations because the computer is offline.": "No se pudieron descargar las traducciones porque el equipo está sin conexión.",
        "FCUpdate successfully installed.": "FCUpdate se ha instalado correctamente.",
        "Please restart FreeCAD for changes to take effect.\nRestart FreeCAD?": "Por favor, reinicia FreeCAD para que los cambios surtan efecto.\n¿Reiniciar FreeCAD?",
        "Restart Required": "Reinicio requerido",
        "Now": "Ahora",
        "Later": "Más tarde",
        "Installation cancelled": "Instalación cancelada",
        "No files have been installed.": "No se ha instalado ningún archivo.",
    },
    'Polish': {
        "FCUpdate installation": "Instalacja FCUpdate",
        "This macro will create a folder in your user space to install the files needed to check for FreeCAD updates. If FCUpdate is already installed, the files will be overwritten. \n Would you like to continue ?":
            "Makro utworzy folder w Twojej przestrzeni użytkownika, aby zainstalować pliki potrzebne do sprawdzania aktualizacji FreeCAD. Jeśli FCUpdate jest już zainstalowany, pliki zostaną nadpisane.\nCzy chcesz kontynuować?",
        "Install language packs": "Zainstaluj pakiety językowe",
        "Yes": "Tak",
        "No": "Nie",
        "Error": "Błąd",
        "No Internet connection": "Brak połączenia z Internetem",
        "Could not download translations because the computer is offline.": "Nie można pobrać tłumaczeń, ponieważ komputer jest offline.",
        "FCUpdate successfully installed.": "FCUpdate został pomyślnie zainstalowany.",
        "Please restart FreeCAD for changes to take effect.\nRestart FreeCAD?": "Uruchom ponownie FreeCAD, aby zmiany zaczęły obowiązywać.\nUruchomić ponownie FreeCAD?",
        "Restart Required": "Wymagane ponowne uruchomienie",
        "Now": "Teraz",
        "Later": "Później",
        "Installation cancelled": "Instalacja anulowana",
        "No files have been installed.": "Nie zainstalowano żadnych plików.",
    },
    'English': {}  # Default value
}

def get_user_language():
    lang = App.ParamGet("User parameter:BaseApp/Preferences/General").GetString("Language", "")
    if lang and lang != "Default":
        return lang
    else:
        'English'

lang = get_user_language()

def tr(text):
    return translations.get(lang, {}).get(text, text)

# --- Class dialog ---
class InstallationDialog(QDialog):
    def __init__(self):
        super().__init__()
        self.setWindowTitle(tr("FCUpdate installation"))
        self.setModal(True)
        self.resize(400, 200)

        layout = QVBoxLayout(self)

        label = QLabel(tr("This macro will create a folder in your user space to install the files needed to check for FreeCAD updates. If FCUpdate is already installed, the files will be overwritten. \n Would you like to continue ?"))
        label.setWordWrap(True)
        layout.addWidget(label)

        self.checkbox = QCheckBox(tr("Install language packs"))
        layout.addWidget(self.checkbox)

        buttons = QtWidgets.QDialogButtonBox(QtWidgets.QDialogButtonBox.Yes | QtWidgets.QDialogButtonBox.No)
        buttons.button(QtWidgets.QDialogButtonBox.Yes).setText(tr("Yes"))
        buttons.button(QtWidgets.QDialogButtonBox.No).setText(tr("No"))
        buttons.accepted.connect(self.accept)
        buttons.rejected.connect(self.reject)
        layout.addWidget(buttons)

    def is_checked(self):
        return self.checkbox.isChecked()

def has_internet_connection(host="8.8.8.8", port=53, timeout=3):
    try:
        socket.setdefaulttimeout(timeout)
        socket.socket(socket.AF_INET, socket.SOCK_STREAM).connect((host, port))
        return True
    except Exception:
        return False

def download_translations(destination_folder):
    api_url = "https://api.github.com/repos/Grubuntu/FCUpdate/contents/translations"
    headers = {'Accept': 'application/vnd.github.v3+json'}

    progress_dialog = QtWidgets.QProgressDialog(
        tr("Downloading translation files..."), tr("Cancel"), 0, 0)
    progress_dialog.setWindowModality(QtCore.Qt.ApplicationModal)
    progress_dialog.setMinimumDuration(0)
    progress_dialog.setValue(0)
    progress_dialog.show()
    QtWidgets.QApplication.processEvents()

    try:
        request = urllib.request.Request(api_url, headers=headers)
        with urllib.request.urlopen(request) as response:
            data = json.loads(response.read().decode())

        total_files = len([f for f in data if f['name'].endswith('.qm') or f['name'].endswith('.ts')])
        progress_dialog.setMaximum(total_files)

        downloaded = 0
        for file_info in data:
            if file_info['name'].endswith('.qm') or file_info['name'].endswith('.ts'):
                if progress_dialog.wasCanceled():
                    break
                download_url = file_info['download_url']
                file_path = destination_folder / file_info['name']
                urllib.request.urlretrieve(download_url, file_path)
                downloaded += 1
                progress_dialog.setValue(downloaded)
                QtWidgets.QApplication.processEvents()
    except Exception as e:
        QtWidgets.QMessageBox.warning(None, tr("Error"), str(e))
    finally:
        progress_dialog.close()


# --- Main code ---
dialog = InstallationDialog()
if dialog.exec() == QDialog.Accepted:
    mod_path = Path(App.getUserAppDataDir()) / "Mod" / "FCUpdate"
    mod_path.mkdir(parents=True, exist_ok=True)

    (mod_path / "InitGui.py").write_text(init_gui_content, encoding='utf-8')
    (mod_path / "FCUpdate.py").write_text(check_update_content, encoding='utf-8')

    if dialog.is_checked():
        if has_internet_connection():
            translations_path = mod_path / "translations"
            translations_path.mkdir(parents=True, exist_ok=True)
            download_translations(translations_path)
        else:
            QtWidgets.QMessageBox.warning(None,
                tr("No Internet connection"),
                tr("Could not download translations because the computer is offline."))

    msg = QMessageBox()
    msg.setIcon(QMessageBox.Information)
    msg.setText(tr("FCUpdate successfully installed."))
    msg.setInformativeText(tr("Please restart FreeCAD for changes to take effect.\nRestart FreeCAD?"))
    msg.setWindowTitle(tr("Restart Required"))
    msg.setStandardButtons(QMessageBox.Yes | QMessageBox.No)

    nowButton = msg.button(QMessageBox.Yes)
    nowButton.setText(tr("Now"))
    laterButton = msg.button(QMessageBox.No)
    laterButton.setText(tr("Later"))

    response = msg.exec()
    if response == QMessageBox.Yes:
        args = QtWidgets.QApplication.arguments()[1:]
        if Gui.getMainWindow().close():
            QtCore.QProcess.startDetached(QtWidgets.QApplication.applicationFilePath(), args)
else:
    QtWidgets.QMessageBox.information(None,
        tr("Installation cancelled"),
        tr("No files have been installed."))
